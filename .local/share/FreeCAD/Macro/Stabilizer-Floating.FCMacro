# -*- coding: utf-8 -*-

# Macro Begin: /home/ifohancroft/.FreeCAD/Macro/Stabilizer-Floating.FCMacro +++++++++++++++++++++++++++++++++++++++++++++++++
import FreeCAD
import Sketcher

# Geometry
(g0,g1,g2,g3,g4,g5,g6,g7,g8,g9,g10,g11,g12,g13,g14,g15,g16,g17,g18,g19,g20,g21,g22,g23,g24,g25,g26,g27,g28,g29,g30,g31,g32,g33,g34,g35,g36) = ActiveSketch.addGeometry([

    Part.LineSegment(App.Vector(-7, 7, 0), App.Vector(7, 7, 0)),
    Part.LineSegment(App.Vector(7, 7, 0), App.Vector(7, 2.3, 0)),
    Part.LineSegment(App.Vector(7, 2.3, 0), App.Vector(8.525, 2.3, 0)),
    Part.LineSegment(App.Vector(8.525, 2.3, 0), App.Vector(8.525, 5.53, 0)),
    Part.LineSegment(App.Vector(8.525, 5.53, 0), App.Vector(15.275, 5.53, 0)),
    Part.LineSegment(App.Vector(15.275, 5.53, 0), App.Vector(15.275, 2.3, 0)),
    Part.LineSegment(App.Vector(15.275, 2.3, 0), App.Vector(16.1, 2.3, 0)),
    Part.LineSegment(App.Vector(16.1, 2.3, 0), App.Vector(16.1, -0.485, 0)),
    Part.LineSegment(App.Vector(16.1, -0.485, 0), App.Vector(15.275, -0.485, 0)),
    Part.LineSegment(App.Vector(15.275, -0.485, 0), App.Vector(15.275, -6.77, 0)),
    Part.LineSegment(App.Vector(15.275, -6.77, 0), App.Vector(13.55, -6.77, 0)),
    Part.LineSegment(App.Vector(13.55, -6.77, 0), App.Vector(13.55, -7.97, 0)),
    Part.LineSegment(App.Vector(13.55, -7.97, 0), App.Vector(10.25, -7.97, 0)),
    Part.LineSegment(App.Vector(10.25, -7.97, 0), App.Vector(10.25, -6.77, 0)),
    Part.LineSegment(App.Vector(10.25, -6.77, 0), App.Vector(8.525, -6.77, 0)),
    Part.LineSegment(App.Vector(8.525, -6.77, 0), App.Vector(8.525, -2.3, 0)),
    Part.LineSegment(App.Vector(8.525, -2.3, 0), App.Vector(7, -2.3, 0)),
    Part.LineSegment(App.Vector(7, -2.3, 0), App.Vector(7, -7, 0)),
    Part.LineSegment(App.Vector(7, -7, 0), App.Vector(-7, -7, 0)),
    Part.LineSegment(App.Vector(-7, -7, 0), App.Vector(-7, -2.3, 0)),
    Part.LineSegment(App.Vector(-7, -2.3, 0), App.Vector(-8.525, -2.3, 0)),
    Part.LineSegment(App.Vector(-8.525, -2.3, 0), App.Vector(-8.525, -6.77, 0)),
    Part.LineSegment(App.Vector(-8.525, -6.77, 0), App.Vector(-10.25, -6.77, 0)),
    Part.LineSegment(App.Vector(-10.25, -6.77, 0), App.Vector(-10.25, -7.97, 0)),
    Part.LineSegment(App.Vector(-10.25, -7.97, 0), App.Vector(-13.55, -7.97, 0)),
    Part.LineSegment(App.Vector(-13.55, -7.97, 0), App.Vector(-13.55, -6.77, 0)),
    Part.LineSegment(App.Vector(-13.55, -6.77, 0), App.Vector(-15.275, -6.77, 0)),
    Part.LineSegment(App.Vector(-15.275, -6.77, 0), App.Vector(-15.275, -0.485, 0)),
    Part.LineSegment(App.Vector(-15.275, -0.485, 0), App.Vector(-16.1, -0.485, 0)),
    Part.LineSegment(App.Vector(-16.1, -0.485, 0), App.Vector(-16.1, 2.3, 0)),
    Part.LineSegment(App.Vector(-16.1, 2.3, 0), App.Vector(-15.275, 2.3, 0)),
    Part.LineSegment(App.Vector(-15.275, 2.3, 0), App.Vector(-15.275, 5.53, 0)),
    Part.LineSegment(App.Vector(-15.275, 5.53, 0), App.Vector(-8.525, 5.53, 0)),
    Part.LineSegment(App.Vector(-8.525, 5.53, 0), App.Vector(-8.525, 2.3, 0)),
    Part.LineSegment(App.Vector(-8.525, 2.3, 0), App.Vector(-7, 2.3, 0)),
    Part.LineSegment(App.Vector(-7, 2.3, 0), App.Vector(-7, 7, 0)),
    Part.Point(App.Vector(0, 0, 0))

], False)

# Constraints
ActiveSketch.addConstraint([

    Sketcher.Constraint('Perpendicular', g0, g1),
    Sketcher.Constraint('Parallel', g2, g0),
    Sketcher.Constraint('Parallel', g3, g1),
    Sketcher.Constraint('Parallel', g4, g0),
    Sketcher.Constraint('Parallel', g5, g1),
    Sketcher.Constraint('Parallel', g6, g0),
    Sketcher.Constraint('Parallel', g7, g1),
    Sketcher.Constraint('Parallel', g8, g0),
    Sketcher.Constraint('Parallel', g9, g1),
    Sketcher.Constraint('Parallel', g10, g0),
    Sketcher.Constraint('Parallel', g11, g1),
    Sketcher.Constraint('Parallel', g12, g0),
    Sketcher.Constraint('Parallel', g13, g1),
    Sketcher.Constraint('Parallel', g14, g0),
    Sketcher.Constraint('Parallel', g15, g1),
    Sketcher.Constraint('Parallel', g16, g0),
    Sketcher.Constraint('Parallel', g17, g1),
    Sketcher.Constraint('Parallel', g18, g0),
    Sketcher.Constraint('Parallel', g19, g1),
    Sketcher.Constraint('Parallel', g20, g0),
    Sketcher.Constraint('Parallel', g21, g1),
    Sketcher.Constraint('Parallel', g22, g0),
    Sketcher.Constraint('Parallel', g23, g1),
    Sketcher.Constraint('Parallel', g24, g0),
    Sketcher.Constraint('Parallel', g25, g1),
    Sketcher.Constraint('Parallel', g26, g0),
    Sketcher.Constraint('Parallel', g28, g0),
    Sketcher.Constraint('Parallel', g29, g1),
    Sketcher.Constraint('Parallel', g30, g0),
    Sketcher.Constraint('Parallel', g31, g1),
    Sketcher.Constraint('Parallel', g32, g0),
    Sketcher.Constraint('Parallel', g33, g1),
    Sketcher.Constraint('Parallel', g34, g0),
    Sketcher.Constraint('Parallel', g35, g1),
    Sketcher.Constraint('Coincident', g0, 2, g1, 1),
    Sketcher.Constraint('Coincident', g1, 2, g2, 1),
    Sketcher.Constraint('Coincident', g2, 2, g3, 1),
    Sketcher.Constraint('Coincident', g3, 2, g4, 1),
    Sketcher.Constraint('Coincident', g4, 2, g5, 1),
    Sketcher.Constraint('Coincident', g5, 2, g6, 1),
    Sketcher.Constraint('Coincident', g6, 2, g7, 1),
    Sketcher.Constraint('Coincident', g7, 2, g8, 1),
    Sketcher.Constraint('Coincident', g8, 2, g9, 1),
    Sketcher.Constraint('Coincident', g9, 2, g10, 1),
    Sketcher.Constraint('Coincident', g10, 2, g11, 1),
    Sketcher.Constraint('Coincident', g11, 2, g12, 1),
    Sketcher.Constraint('Coincident', g12, 2, g13, 1),
    Sketcher.Constraint('Coincident', g13, 2, g14, 1),
    Sketcher.Constraint('Coincident', g14, 2, g15, 1),
    Sketcher.Constraint('Coincident', g15, 2, g16, 1),
    Sketcher.Constraint('Coincident', g16, 2, g17, 1),
    Sketcher.Constraint('Coincident', g17, 2, g18, 1),
    Sketcher.Constraint('Coincident', g18, 2, g19, 1),
    Sketcher.Constraint('Coincident', g19, 2, g20, 1),
    Sketcher.Constraint('Coincident', g20, 2, g21, 1),
    Sketcher.Constraint('Coincident', g21, 2, g22, 1),
    Sketcher.Constraint('Coincident', g22, 2, g23, 1),
    Sketcher.Constraint('Coincident', g23, 2, g24, 1),
    Sketcher.Constraint('Coincident', g24, 2, g25, 1),
    Sketcher.Constraint('Coincident', g25, 2, g26, 1),
    Sketcher.Constraint('Coincident', g26, 2, g27, 1),
    Sketcher.Constraint('Coincident', g27, 2, g28, 1),
    Sketcher.Constraint('Coincident', g28, 2, g29, 1),
    Sketcher.Constraint('Coincident', g29, 2, g30, 1),
    Sketcher.Constraint('Coincident', g30, 2, g31, 1),
    Sketcher.Constraint('Coincident', g31, 2, g32, 1),
    Sketcher.Constraint('Coincident', g32, 2, g33, 1),
    Sketcher.Constraint('Coincident', g33, 2, g34, 1),
    Sketcher.Constraint('Coincident', g34, 2, g35, 1),
    Sketcher.Constraint('Coincident', g35, 2, g0, 1),
    Sketcher.Constraint('Distance', g0, 14),
    Sketcher.Constraint('Distance', g1, 4.7),
    Sketcher.Constraint('Distance', g2, 1.525),
    Sketcher.Constraint('Distance', g3, 3.23),
    Sketcher.Constraint('Distance', g4, 6.75),
    Sketcher.Constraint('Equal', g5, g3),
    Sketcher.Constraint('Distance', g6, 0.825),
    Sketcher.Constraint('Distance', g7, 2.785),
    Sketcher.Constraint('Equal', g8, g6),
    Sketcher.Constraint('Distance', g9, 6.285),
    Sketcher.Constraint('Distance', g10, 1.725),
    Sketcher.Constraint('Distance', g11, 1.2),
    Sketcher.Constraint('Distance', g12, 3.3),
    Sketcher.Constraint('Equal', g13, g11),
    Sketcher.Constraint('Equal', g14, g10),
    Sketcher.Constraint('Distance', g15, 4.47),
    Sketcher.Constraint('Equal', g16, g2),
    Sketcher.Constraint('Equal', g17, g1),
    Sketcher.Constraint('Equal', g18, g0),
    Sketcher.Constraint('Equal', g19, g1),
    Sketcher.Constraint('Equal', g20, g2),
    Sketcher.Constraint('Equal', g21, g15),
    Sketcher.Constraint('Equal', g22, g10),
    Sketcher.Constraint('Equal', g23, g11),
    Sketcher.Constraint('Equal', g24, g12),
    Sketcher.Constraint('Equal', g25, g11),
    Sketcher.Constraint('Equal', g26, g10),
    Sketcher.Constraint('Equal', g28, g6),
    Sketcher.Constraint('Equal', g29, g7),
    Sketcher.Constraint('Equal', g30, g6),
    Sketcher.Constraint('Equal', g31, g3),
    Sketcher.Constraint('Equal', g32, g4),
    Sketcher.Constraint('Equal', g33, g3),
    Sketcher.Constraint('Equal', g34, g2),
    Sketcher.Constraint('Equal', g35, g1),
    Sketcher.Constraint('Symmetric', g0, 2, g18, 2, g36, 1)

])

# Macro End: /home/ifohancroft/.FreeCAD/Macro/Stabilizer-Floating.FCMacro +++++++++++++++++++++++++++++++++++++++++++++++++
